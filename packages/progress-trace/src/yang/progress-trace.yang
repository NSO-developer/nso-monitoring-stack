module progress-trace {

  namespace "http://example.com/progress-trace";
  prefix progress-trace;

  import ietf-inet-types {
    prefix inet;
  }
  import tailf-common {
    prefix tailf;
  }
  import tailf-ncs {
    prefix ncs;
  }

  description
    "Bla bla...";

  revision 2016-01-01 {
    description
      "Initial revision.";
  }

  container test {
    tailf:action report {
      tailf:actionpoint report-action;
      input {
        leaf msg {
          type string;
        }
      }
    }
  }
}
